// Copyright 2024 The OpenConfig Authors 
//
// Licensed under the Apache License, Version 2.0 (the "License");
// you may not use this file except in compliance with the License.
// You may obtain a copy of the License at
//
//    http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.
module gsii-interfaces-proto {
  namespace "http://github.com/openconfig/gsii/v1/obj/interfaces/proto";
  prefix "gsii-int-proto";

  import openconfig-interfaces { prefix "oc-if"; }
  import gsii-interfaces { prefix "gsii-if"; }

  organization
    "OpenConfig working group";
  
  contact
    "www.openconfig.net";

  description
    "This module defines deviations that allow for gSII protobufs
    to be generated for the OpenConfig path /interfaces/interface.";
  
  

  // This approach results in a proto that includes the "volatile" container.
  container interfaces {
    list interface {
      key "name";

      leaf name { type string; }

      uses gsii-if:interfaces-structural;
    }
  }
}
