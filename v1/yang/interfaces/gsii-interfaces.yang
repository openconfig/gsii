// Copyright 2024 The OpenConfig Authors 
//
// Licensed under the Apache License, Version 2.0 (the "License");
// you may not use this file except in compliance with the License.
// You may obtain a copy of the License at
//
//    http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.
module gsii-interfaces {
  namespace "http://github.com/openconfig/gsii/v1/obj/interfaces";
  prefix "gsii-if";

  import openconfig-interfaces { prefix "oc-if"; }

  organization
    "OpenConfig working group";
  
  contact
    "www.openconfig.net";
  
  description
    "This module defines fields that can be manipulated by the
    gSII interface as defined in github.com/openconfig/gsii.

    The module augments the openconfig-interfaces module, adding
    new volatile leaves. To generate a protobuf the deviation module
    gsii-interfaces-proto.yang should also be used.";
  
  grouping interfaces-structural {
    container volatile {
      // Volatile containers are marked `config false` in since
      // they are not writeable via gNMI.
      config false;

      uses interfaces-volatile;
    }
  }

  grouping interfaces-volatile {
    description
      "Parameters directly related to an interface that are
      exposed via gSII.";

    leaf enabled {
      type boolean;
      description
        "The intended state of a network interface. When set to
        true the interface is administratively 'UP', when set to
        false the interface is administratively disabled.";
    }
  }

  // Augment the YANG tree with the volatile leaves for volatile
  // configuration - as manipulated by gSII.
  augment "/oc-if:interfaces/oc-if:interface" {
    uses interfaces-structural;
  }

}
